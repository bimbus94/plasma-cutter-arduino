############################################--Generowanie Gcode--############################
# import statements
import Part
import FreeCAD
from FreeCAD import Base
from PySide import QtGui, QtCore

# UI Class definitions

class WindowGcode(QtGui.QDialog):
	""""""
	def __init__(self):
		super(WindowGcode, self).__init__()
		self.initUI()
	def initUI(self):
		self.result = userCancelled
		# create our window
		# define window		xLoc,yLoc,xDim,yDim
		self.setGeometry(	250, 150, 600, 600)
		self.setWindowTitle("Generator Gcode")
		self.setWindowFlags(QtCore.Qt.WindowStaysOnTopHint)


		#Dane cietej rury

		self.glabel1 = QtGui.QLabel("1. Podstawowe dane", self)
		self.glabel1.move(20, 10)

		self.glabel2 = QtGui.QLabel("Liczba pkt-ow dyskretyzacji:", self)
		self.glabel2.move(20, 30)

		self.glabel3 = QtGui.QLabel("Nazwa pliku do zapisu:", self)
		self.glabel3.move(20, 60)

		self.glabel4 = QtGui.QLabel("Sciezka dostepu NIE DZIALA:", self)
		self.glabel4.move(20, 90)

		self.numberOfPoints = QtGui.QLineEdit(self)
		self.numberOfPoints.setInputMask("999")
		self.numberOfPoints.setText("100")
		self.numberOfPoints.setFixedWidth(50)
		self.numberOfPoints.move(250, 30)

		self.fileName = QtGui.QLineEdit(self)
		self.fileName.setText("123.txt")
		self.fileName.setFixedWidth(50)
		self.fileName.move(250, 60)
		

		self.path = QtGui.QLineEdit(self)
		self.path.setText("abc")
		self.path.setFixedWidth(50)
		self.path.move(250, 90)

		self.glabel5 = QtGui.QLabel("2. Wybierz rodzaj rozwiniecia Y:", self)
		self.glabel5.move(20, 140)
		self.gbutton1 = QtGui.QRadioButton("[1] Y w [stopnie] 0-360", self)
		#self.gcheckbox1.clicked.connect(self.gonCheckbox1)
		self.gbutton1.move(40, 170)
		
		self.gbutton2 = QtGui.QRadioButton("[2] Y w [stopnie] (-180)-(180)", self)
		#self.gcheckbox2.clicked.connect(self.gonCheckbox2)
		self.gbutton2.move(40, 200)
		
		self.gbutton3 = QtGui.QRadioButton("[3] Y rozwiniete w [mm] 0-(2*pi*R)", self)
		#self.gcheckbox3.clicked.connect(self.gonCheckbox3)
		self.gbutton3.move(40, 230)
		
		self.gbutton4 = QtGui.QRadioButton("[4] Y rozwiniete w [mm] (-pi*R)-(pi*R)", self)
		#self.gcheckbox4.clicked.connect(self.gonCheckbox4)
		self.gbutton4.move(40, 260)

		self.gbutton5 = QtGui.QRadioButton("[5] X i Y pozostawione bez zmian w [mm]", self)
		#self.gcheckbox5.clicked.connect(self.gonCheckbox5)
		self.gbutton5.move(40, 290)
		
		self.glabel6 = QtGui.QLabel("3. Paramatery obrobki", self)
		self.glabel6.move(20, 320)

		self.glabel7 = QtGui.QLabel("Posuw dla osi X [mm/min]", self)
		self.glabel7.move(20, 350)

		self.glabel8 = QtGui.QLabel("Posuw dla osi Y [mm/min] lub [stop/min]", self)
		self.glabel8.move(20, 380)

		self.glabel9 = QtGui.QLabel("lub [stop/min]", self)
		self.glabel9.move(20, 400)

		self.feedX= QtGui.QLineEdit(self)
		self.fileName.setInputMask("9999")
		self.feedX.setText("1000")
		self.feedX.setFixedWidth(50)
		self.feedX.move(250, 350)

		self.feedY = QtGui.QLineEdit(self)
		self.path.setInputMask("9999")
		self.feedY.setText("1000")
		self.feedY.setFixedWidth(50)
		self.feedY.move(250, 380)

		# cancel button
		gcancelButton = QtGui.QPushButton('Cancel', self)
		gcancelButton.clicked.connect(self.gonCancel)
		gcancelButton.setAutoDefault(True)
		gcancelButton.move(260, 550)
		# OK button
		gokButton = QtGui.QPushButton('OK', self)
		gokButton.clicked.connect(self.gonOk)
		gokButton.move(150, 550)
		# now make the window visible
		self.show()

	def gonCheckbox1(self):	
		return True

	def gonCheckbox2(self):
		return True

	def gonCheckbox3(self):
		return True

	def gonCheckbox4(self):
		return True

	def gonCheckbox5(self):
		return True


	def gonCancel(self):
		self.result = userCancelled
		self.close()
	def gonOk(self):
		self.result = "OKEY"
		self.close()


userCancelled = "Cancelled"
userOK = "OK"
# code ***********************************************************************************

form2 = WindowGcode()
form2.exec_()

if form2.result == userCancelled:
	pass # steps to handle user clicking Cancel

if (form2.result == "OKEY"):	
	print("OK")
	
	name=str(form2.fileName.text())
	path=str(form2.path.text())
	feedX=int(form2.feedX.text())
	feedY=int(form2.feedY.text())


 #PySide.QtGui.QAbstractButton.isChecked()


##############################################################################################


import numpy as np
#cartesian to radius and angle (0-2*PI)  or (-Pi-Pi when negativeRangeIn.. is true)
def cart2pol(x, y, negativeRangeInRad=False, negativeRangeInDeg=False):
    rho = np.sqrt(x**2 + y**2)
    phi = np.arctan2(y, x)
    if (negativeRangeInRad or negativeRangeInDeg):
	if phi<0.0:
		phi=phi+2*np.pi
    return(rho, phi)

#cartesian to curve_lenght=radius*degree and z coordinates; 0-2Pi*R or -Pi*R-Pi*R when negativeRange... is true
def cart2curve_len(x,y, negativeRangeInLen=False):
	rho, phi = cart2pol(x,y,negativeRangeInLen)
	curve_len=rho*phi
	return (curve_len)

#cartesian to radius and angle in degree (0-360 deg) or (-180-180deg when negativeRangeIn.. is true)
def cart2polDeg(x,y, negativeRangeInRad=False, negativeRangeInDeg=False):
    rho = np.sqrt(x**2 + y**2)
    phi = np.arctan2(y, x)
    if (negativeRangeInRad or negativeRangeInDeg):    
	if phi<0.0:
		phi=phi+2*np.pi
    phi=phi*180.0/np.pi
    #return(rho, phi)
    return phi

#polar to cartesian x,y

def pol2cart(rho, phi):
    x = rho * np.cos(phi)
    y = rho * np.sin(phi)
    return(x, y)


###Pobranie i dyskretyzacja punktow
import Draft
numberOfPoints = 100
#select curve
s=0

allPoints=[]
wire=[]
for wires in FreeCADGui.Selection.getSelectionEx()[0].SubObjects:
	selectedEdge = wires.copy()
	points = selectedEdge.discretize(numberOfPoints)		
	i=0
	row=[]
	pointsList=[]
	for k in points:
		row=[i, k.x, k.y, k.z]
		wire.append(k) # append the coordinates
		pointsList.append(row)
		i+=1
		print i, " X", k.x, " Y", k.y, " Z", k.z
	allPoints.append(pointsList)
	wireAll=Draft.makeWire(wire,closed=False,face=False,support=None)   # create the wire open
	#Draft.makeWire(wire,closed=True,face=False,support=None)   # create the wire closed (uncomment for use)
	wire=[]



###Zmiana wspolrzednych kartenzjanskich na polarne; X pozostaje takie samo; zmiana YZ na kat 0-360 stopni
###W Gcodze X to wspolrzedna wzdluz rury w [mm], przy Y stoi kat obrotu
allPointsPolDeg=[]
wire=[]

for p in allPoints:
	pointsList=[]
	row=[]
	for r in p:
		print r[0], " X", r[1], " Y" ,cart2polDeg(r[2], r[3], form2.gbutton1.isChecked(),form2.gbutton3.isChecked())
		row=[r[0], r[1], cart2polDeg(r[2], r[3], form2.gbutton1.isChecked(),form2.gbutton3.isChecked())]
		wire.append(Base.Vector(r[1],cart2polDeg(r[2], r[3],form2.gbutton1.isChecked(),form2.gbutton3.isChecked()),0)) # append the coordinates
		pointsList.append(row)
	allPointsPolDeg.append(pointsList)
	wireDeg=Draft.makeWire(wire,closed=False,face=False,support=None)   # create the wire open
	#Draft.makeWire(wire,closed=True,face=False,support=None)   # create the wire closed (uncomment for use)
	wire=[]


###W Gcodze X to wspolrzedna wzdluz rury w [mm], przy Y to rozwiniecie rury w [mm]=r*kat obrotu [rad]
allPointsCurve_Len=[]
wire=[]
for p in allPoints:
	pointsList=[]
	row=[]
	for r in p:
		print r[0], " X", r[1], " Y" ,cart2curve_len(r[2], r[3], form2.gbutton3.isChecked())
		row=[r[0], r[1], cart2curve_len(r[2], r[3], form2.gbutton3.isChecked())]
		wire.append(Base.Vector(r[1],cart2curve_len(r[2], r[3], form2.gbutton3.isChecked()),0)) # append the coordinates
		pointsList.append(row)
	allPointsCurve_Len.append(pointsList)
	wireLen=Draft.makeWire(wire,closed=False,face=False,support=None)   # create the wire open
	#Draft.makeWire(wire,closed=True,face=False,support=None)   # create the wire closed (uncomment for use)
	wire=[]

#Wybranie rodzaju punktow do zapisu w zaleznosci od wybranej w oknie opcji
generatePoints=[]

if form2.gbutton1.isChecked() or form2.gbutton2.isChecked():
	generatePoints=allPointsPolDeg
	print("wybrano allPointsPolDeg")
	#Part.show(wireDeg)
elif form2.gbutton3.isChecked() or form2.gbutton4.isChecked():
	generatePoints=allPointsCurve_Len
	print("wybrano allPointsPolLen")
	#Part.show(wireLen)
else:
	generatePoints=allPoints
	print("wybrano allPoints")
	#Part.show(wireAll)




################ZAPIS DO PLIKU###############
import os
path=os.getcwd()+"/"+name+".txt"
#dodac zmienna path
#path='./1234.txt'
with open(path, 'w') as gcode_file:
	###zapis ustawien czy w Y w mm czy w stopniach####
	#dobranie predkosci posuwow itp####
	####zerowanie programu lub bedzie w arduino juz ;)####
	gcode_file.write('GXX\n')
	for p in generatePoints: ### trzeba zmienic all points na cos ogolniejszego####
		###najazd szybki na punkt poczatkowy####
		gcode_file.write('G00 X%.1f Y%.2f\n' % (float(p[0][1]), float(p[0][2])))
		####wlaczenie palinka####		
		gcode_file.write('Mxx\n')
		for r in p[1:]: 
			gcode_file.write("G01 X%.1f Y%.2f\n" % (float(r[1]), float(r[2])))
		####wylaczenie palnika####		
		gcode_file.write('Mxx\n')
	###wrocenie na pozycje 0###
	gcode_file.write('G00 X0.0 Y0.0')
		


print("Sciezka dostepu do pliku to " + path)
